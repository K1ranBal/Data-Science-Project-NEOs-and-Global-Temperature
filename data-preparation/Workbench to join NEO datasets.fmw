FME workspace Workbench to join NEO datasets.fmw

Parameters:
- DestDataset_CSV2 =
- SourceDataset_CSV2 =
- SourceDataset_CSV2_4 =
- SourceDataset_CSV2_5 =

Readers:
- CSV2_1: CSV2 from $(SourceDataset_CSV2)
- CSV2_2: CSV2 from $(SourceDataset_CSV2_5)
- CSV2_3: CSV2 from $(SourceDataset_CSV2_4)

Writers:
- CSV2_4: CSV2 to $(DestDataset_CSV2)

CSV (reader CSV2_1)
    attributes: id real64, name varchar(33), est_diameter_min real64, est_diameter_max real64, relative_velocity real64, miss_distance real64, orbiting_body varchar(6), sentry_object varchar(6), absolute_magnitude real32, hazardous varchar(6)
    -> FeatureJoiner [LEFT]
CSV (reader CSV2_2)
    attributes: col0 uint32, id real64, neo_reference_id real64, name varchar(33), name_limited varchar(18), designation varchar(11), absolute_magnitude_h real32, is_potentially_hazardous_asteroid varchar(6), is_sentry_object varchar(6), kilometers_estimated_diameter_min real64, kilometers_estimated_diameter_max real64, orbit_id uint32, orbit_class_type varchar(4), perihelion_distance real64, aphelion_distance real64, first_observation_date varchar(11), last_observation_date varchar(11), orbit_class_description varchar(91)
    -> AttributeRenamer
AttributeRenamer
    ATTR_TABLE = RENAME_SET_DEFAULT name > name_NEO_ECA
    MISSING_INPUT_ATTRS = REMOVE
    -> FeatureJoiner [RIGHT]
FeatureJoiner
    ATTR_CONFLICT_RES = Use Left
    GEOMETRY_HANDLING = Use Left
    JOIN_KEYS = id neo_reference_id AUTO
    JOIN_MODE = Left
    JOINED -> AttributeFilter
AttributeFilter
    ATTR_NAME = neo_reference_id
    ATTR_VALUES = <Empty>,<Missing>,<Null>,<Unfiltered>
    <UNFILTERED> -> FeatureJoiner_2 [LEFT]
CSV (reader CSV2_3)
    attributes: Object varchar(28), Close-Approach (CA) Date varchar(35), CA DistanceNominal (au) real32, CA DistanceMinimum (au) real64, V relative(km/s) real32, V infinity(km/s) real32, H(mag) varchar(5), Diameter varchar(18), Rarity varchar(4)
    -> Sorter
Sorter
    SORT_PARM = Object NATURAL ASCENDING "Close-Approach (CA) Date" NATURAL DESCENDING
    SORTED -> DuplicateFilter
DuplicateFilter
    INPUT_ORDERED_CHOICE = Yes
    KEYATTR = Object
    UNIQUE -> FeatureJoiner_2 [RIGHT]
FeatureJoiner_2
    ATTR_CONFLICT_RES = Use Left
    GEOMETRY_HANDLING = Use Left
    JOIN_KEYS = name Object AUTO
    JOIN_MODE = Left
    JOINED -> AttributeFilter_2
AttributeFilter_2
    ATTR_NAME = Object
    ATTR_VALUES = <Empty>,<Missing>,<Null>,<Unfiltered>
    <UNFILTERED> -> NASA Joined Datasets (writer CSV2_4)
NASA Joined Datasets (writer CSV2_4)
    attributes: id real64, name varchar(33), est_diameter_min real64, est_diameter_max real64, relative_velocity real64, miss_distance real64, orbiting_body varchar(6), sentry_object varchar(6), absolute_magnitude real32, hazardous varchar(6), name_NEO_ECA varchar(33), neo_reference_id real64, designation varchar(11), absolute_magnitude_h real32, is_potentially_hazardous_asteroid varchar(6), is_sentry_object varchar(6), kilometers_estimated_diameter_min real64, kilometers_estimated_diameter_max real64, orbit_id uint32, orbit_class_type varchar(4), perihelion_distance real64, aphelion_distance real64, first_observation_date varchar(11), last_observation_date varchar(11), orbit_class_description varchar(91), Object varchar(28), Close-Approach (CA) Date varchar(35), CA DistanceNominal (au) real32, CA DistanceMinimum (au) real64, V relative(km/s) real32,
      V infinity(km/s) real32, H(mag) varchar(5), Diameter varchar(18), Rarity varchar(4)
